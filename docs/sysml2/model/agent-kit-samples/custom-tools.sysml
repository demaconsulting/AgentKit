package AgentKitSamples {
    part def CustomTools {
        doc /* Console chat sample demonstrating how an application author writes their own guarded tools with GuardedToolFactory and publishes them as packs that compose alongside a shipped pack, for both a path-taking tool and a tool that takes no path. */

        comment sourceRef /* Source: samples/custom-tools/ (a folder of several source files, not a single file: a sample is a complete runnable application read as one worked example) */
        comment testRef /* Test: test/DemaConsulting.AgentKit.Samples.CustomTools.Tests/ (the sample's test project folder) */
        comment designRef /* Design: docs/design/agent-kit-samples/custom-tools.md */
        comment verificationRef /* Verification: docs/verification/agent-kit-samples/custom-tools.md */
        comment reqRef /* Requirements: docs/reqstream/agent-kit-samples/custom-tools.yaml */
    }
}
