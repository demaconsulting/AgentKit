package AgentKitCore {
    part def RealPathResolver {
        doc /* Resolves a path to an absolute, normalized location, with relative segments collapsed, so that containment is judged between locations spelled the same way. */

        comment sourceRef /* Source: src/DemaConsulting.AgentKit.Core/RealPathResolver.cs */
        comment testRef /* Test: test/DemaConsulting.AgentKit.Core.Tests/RealPathResolverTests.cs */
        comment designRef /* Design: docs/design/agent-kit-core/real-path-resolver.md */
        comment verificationRef /* Verification: docs/verification/agent-kit-core/real-path-resolver.md */
        comment reqRef /* Requirements: docs/reqstream/agent-kit-core/real-path-resolver.yaml */
    }
}
