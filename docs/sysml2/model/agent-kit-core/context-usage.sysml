package AgentKitCore {
    part def ContextUsage {
        doc /* The one shape every provider session answers with - tokens occupied, window size, and the tokens the conversation occupies. Carrying the conversation is what keeps every rotation comparison within one currency, because the split is made by whoever produced the totals. */

        comment sourceRef /* Source: src/DemaConsulting.AgentKit.Core/ContextUsage.cs */
        comment testRef /* Test: test/DemaConsulting.AgentKit.Core.Tests/ContextUsageTests.cs */
        comment designRef /* Design: docs/design/agent-kit-core/context-usage.md */
        comment verificationRef /* Verification: docs/verification/agent-kit-core/context-usage.md */
        comment reqRef /* Requirements: docs/reqstream/agent-kit-core/context-usage.yaml */
    }
}
