package AgentKitCore {
    part def Demo {
        doc /* Demonstration greeting class showing how a DEMA Consulting .NET library class should be structured, documented, and tested. */

        comment sourceRef /* Source: src/DemaConsulting.AgentKit.Core/Demo.cs */
        comment testRef /* Test: test/DemaConsulting.AgentKit.Core.Tests/DemoTests.cs */
        comment designRef /* Design: docs/design/agent-kit-core/demo.md */
        comment verificationRef /* Verification: docs/verification/agent-kit-core/demo.md */
        comment reqRef /* Requirements: docs/reqstream/agent-kit-core/demo.yaml */
    }
}
