package AgentKitCore {
    part def ToolResult {
        doc /* Constructs the results a guarded tool returns to the model - text, structured data, binary content, a caption accompanied by an image, or a refusal - and also defines the DenialReason enumeration naming why a tool refused an operation. */

        comment sourceRef /* Source: src/DemaConsulting.AgentKit.Core/ToolResult.cs */
        comment testRef /* Test: test/DemaConsulting.AgentKit.Core.Tests/ToolResultTests.cs */
        comment designRef /* Design: docs/design/agent-kit-core/tool-result.md */
        comment verificationRef /* Verification: docs/verification/agent-kit-core/tool-result.md */
        comment reqRef /* Requirements: docs/reqstream/agent-kit-core/tool-result.yaml */
    }
}
