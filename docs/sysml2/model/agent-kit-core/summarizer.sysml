package AgentKitCore {
    part def Summarizer {
        doc /* The injected out-of-session consolidation contract, the request that carries the material as a body of peers together with an aggressiveness clause and the target tier, and the consolidation prompt that licenses collapsing repetition, names the specific content that must survive, and asks for terseness by instruction rather than a target size. */

        comment sourceRef /* Source: src/DemaConsulting.AgentKit.Core/Summarizer.cs */
        comment testRef /* Test: test/DemaConsulting.AgentKit.Core.Tests/SummarizerTests.cs */
        comment designRef /* Design: docs/design/agent-kit-core/summarizer.md */
        comment verificationRef /* Verification: docs/verification/agent-kit-core/summarizer.md */
        comment reqRef /* Requirements: docs/reqstream/agent-kit-core/summarizer.yaml */
    }
}
