package AgentKitCore {
    part def ToolName {
        doc /* Defines the family-prefixed tool naming convention and validates names against it, rejecting names that would collide with the bare file access tool names published by the Agent Framework. */

        comment sourceRef /* Source: src/DemaConsulting.AgentKit.Core/ToolName.cs */
        comment testRef /* Test: test/DemaConsulting.AgentKit.Core.Tests/ToolNameTests.cs */
        comment designRef /* Design: docs/design/agent-kit-core/tool-name.md */
        comment verificationRef /* Verification: docs/verification/agent-kit-core/tool-name.md */
        comment reqRef /* Requirements: docs/reqstream/agent-kit-core/tool-name.yaml */
    }
}
