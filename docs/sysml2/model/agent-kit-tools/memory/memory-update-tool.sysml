package AgentKitTools {
    part def MemoryUpdateTool {
        doc /* Publishes the memory_update tool: replaces a memory's detail payload while leaving its descriptor, its provenance and its vector untouched, embedding nothing, and echoes back what the memory is still filed under and still cites. */

        comment sourceRef /* Source: src/DemaConsulting.AgentKit.Tools/Memory/MemoryUpdateTool.cs */
        comment testRef /* Test: test/DemaConsulting.AgentKit.Tools.Tests/Memory/MemoryUpdateToolTests.cs */
        comment designRef /* Design: docs/design/agent-kit-tools/memory/memory-update-tool.md */
        comment verificationRef /* Verification: docs/verification/agent-kit-tools/memory/memory-update-tool.md */
        comment reqRef /* Requirements: docs/reqstream/agent-kit-tools/memory/memory-update-tool.yaml */
    }
}
