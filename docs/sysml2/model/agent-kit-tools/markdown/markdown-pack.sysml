package AgentKitTools {
    part def MarkdownPack {
        doc /* Publishes the markdown tool family as one pack: the single outline tool, governed by the supplied policy, requiring no host capability. */

        comment sourceRef /* Source: src/DemaConsulting.AgentKit.Tools/Markdown/MarkdownPack.cs */
        comment testRef /* Test: test/DemaConsulting.AgentKit.Tools.Tests/Markdown/MarkdownPackTests.cs */
        comment designRef /* Design: docs/design/agent-kit-tools/markdown/markdown-pack.md */
        comment verificationRef /* Verification: docs/verification/agent-kit-tools/markdown/markdown-pack.md */
        comment reqRef /* Requirements: docs/reqstream/agent-kit-tools/markdown/markdown-pack.yaml */
    }
}
