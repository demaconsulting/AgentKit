package AgentKitTools {
    part def AgentProfile {
        doc /* One named agent an application is willing to have started on its behalf: the instructions it is given, the names of the tools it may use, an optional narrower set of path grants than its parent holds, and an optional description shown to the model beside the name. */

        comment sourceRef /* Source: src/DemaConsulting.AgentKit.Tools/Agent/AgentProfile.cs */
        comment testRef /* Test: test/DemaConsulting.AgentKit.Tools.Tests/Agent/AgentProfileTests.cs */
        comment designRef /* Design: docs/design/agent-kit-tools/agent/agent-profile.md */
        comment verificationRef /* Verification: docs/verification/agent-kit-tools/agent/agent-profile.md */
        comment reqRef /* Requirements: docs/reqstream/agent-kit-tools/agent/agent-profile.yaml */
    }
}
